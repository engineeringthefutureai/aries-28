"""Swing one bay's carrier and board out of the rack, as a visual check.

Run from the FreeCAD GUI with the Rack_Assembly document open -- build it
first with hardware/generate_rack.py. Set RECORD_GIF to also write an animated
GIF next to the generators; that needs ffmpeg on PATH.

The animation rests at each end of the motion rather than running the whole
cycle at one speed, so there is time to read what happened before it moves
again. The PAUSE_* settings say for how long.

Frames are rendered SUPERSAMPLE times oversize and scaled back down by ffmpeg,
which is what keeps the edges smooth -- see the note on that setting.

The macro drives Placement by hand, which means temporarily removing the
placement expressions that position the carrier and the blade. They are put
back when the animation finishes, including if it fails part-way -- without
that, running this once would silently unparameterise the assembly.
"""

import math
import os
import shutil
import subprocess
import sys
import tempfile
import time

import FreeCAD as App
import FreeCADGui as Gui

# --- Configuration ---
RECORD_GIF = True
FRAME_SIZE = (720, 1000)   # portrait: the rack is far taller than it is wide
FRAME_RATE = 20
# saveImage renders the view with no anti-aliasing, so straight to FRAME_SIZE
# every sloped edge comes out a staircase -- a 1280x720 frame of this model
# holds only ~640 distinct colours, which is the giveaway. Render this many
# times oversize instead and let ffmpeg lanczos it back down: the averaging on
# the way down is the anti-aliasing. Costs render time and temp space roughly
# with the square of it, so 3 is about the point of diminishing returns.
SUPERSAMPLE = 3
BAY = 2              # which bay to take out, counting from the bottom
SWING_ANGLE = 45.0   # degrees the carrier rotates about the front-right rod
SWING_FRAMES = 16
PULL_FRAMES = 8      # steps spent sliding the carrier off the rods
RETURN_SPEEDUP = 4   # the return legs play back this many times faster

# How long the animation rests at each end of the motion, in seconds. Every
# frame of a GIF written this way is on screen for the same 1/FRAME_RATE, so a
# pause is not a duration but a number of repeated frames -- see hold().
PAUSE_START = 0.5    # seated in the rack, before anything moves
PAUSE_SWUNG = 0.5    # swung open, before the carrier comes off the rods
PAUSE_OUT = 1.5      # fully withdrawn, the frame worth looking at
PAUSE_HOME = 2.0     # home again, so the loop reads as a loop and not a stutter
# ---------------------

try:
    _MACRO_DIR = os.path.dirname(os.path.abspath(__file__))
except NameError:  # some FreeCAD builds run macros without __file__
    _MACRO_DIR = os.getcwd()

_HARDWARE_ROOT = os.path.dirname(_MACRO_DIR)
if _HARDWARE_ROOT not in sys.path:
    sys.path.insert(0, _HARDWARE_ROOT)

import hardware_utils

GIF_OUTPUT = os.path.join(_HARDWARE_ROOT, "animation.gif")
FRAME_DIR = os.path.join(tempfile.gettempdir(), "freecad_anim")


def _pivot_and_step(doc):
    """Rotation centre (the front-right rod) and how far to pull per step."""
    params = doc.getObject("Parametric_PCB")
    if not params:
        App.Console.PrintError("Parametric_PCB (Original) not found.\n")
        return None, None

    rods = doc.getObject("Support_Rods")
    rod_diameter = float(rods.Diameter) if rods else hardware_utils.DEFAULT_ROD_DIAMETER
    gap = float(rods.Gap) if rods else hardware_utils.DEFAULT_ROD_GAP

    # Same helper the plates use, so the pivot cannot drift from the geometry.
    centers = hardware_utils.calculate_rod_centers(
        float(params.Width), float(params.Length), rod_diameter, gap)
    return centers[1], rod_diameter / 4.0


def _release_placement(obj):
    """Strip `obj`'s placement expressions, returning them for restoration."""
    saved = [(path, expr) for path, expr in obj.ExpressionEngine
             if path.startswith("Placement")]
    for path, _expr in saved:
        obj.setExpression(path, None)
    return saved


def _restore_placement(obj, saved, placement):
    obj.Placement = placement
    for path, expr in saved:
        obj.setExpression(path, expr)


def _encode_gif(frame_count):
    if not frame_count:
        return
    ffmpeg = shutil.which("ffmpeg")
    if not ffmpeg:
        App.Console.PrintWarning(
            f"ffmpeg not found on PATH; {frame_count} frames left in {FRAME_DIR}\n")
        return

    pattern = os.path.join(FRAME_DIR, "frame_%04d.png")
    palette = os.path.join(FRAME_DIR, "palette.png")
    # Downscale from the oversized frames on the way in, both times: the
    # palette has to be chosen from the same pixels that will be quantised
    # against it, or it is a palette for a picture nobody sees.
    scale = f"scale={FRAME_SIZE[0]}:{FRAME_SIZE[1]}:flags=lanczos"
    try:
        subprocess.run([ffmpeg, "-v", "warning", "-y", "-i", pattern,
                        "-vf", f"{scale},palettegen=max_colors=256", palette], check=True)
        subprocess.run([ffmpeg, "-v", "warning", "-y",
                        "-framerate", str(FRAME_RATE), "-i", pattern,
                        "-i", palette,
                        # diff_mode keeps the held frames nearly free: only the
                        # rectangle that actually changed gets re-encoded.
                        "-lavfi", f"{scale}[s];[s][1:v]paletteuse="
                                  "dither=sierra2_4a:diff_mode=rectangle",
                        GIF_OUTPUT], check=True)
    except subprocess.CalledProcessError as exc:
        App.Console.PrintError(
            f"ffmpeg failed ({exc.returncode}); frames left in {FRAME_DIR}\n")
        return
    App.Console.PrintMessage(f"Wrote {GIF_OUTPUT}\n")


def run_animation():
    if not App.GuiUp:
        App.Console.PrintError("animate_carrier needs the FreeCAD GUI.\n")
        return

    doc = App.ActiveDocument
    if not doc:
        App.Console.PrintError("No active document.\n")
        return

    # Bay instances are labelled, not named: the clone in the bay is what
    # moves, while the master stays parked off the rack.
    carrier = hardware_utils.find_by_label(doc, f"Carrier_Bay{BAY}")
    blade = hardware_utils.find_by_label(doc, f"Blade_Bay{BAY}")
    if not carrier or not blade:
        App.Console.PrintError(
            f"Bay {BAY} is not occupied -- no Carrier_Bay{BAY}/Blade_Bay{BAY} "
            "in this document.\n")
        return

    pivot, step_dist = _pivot_and_step(doc)
    if pivot is None:
        return

    if RECORD_GIF:
        if os.path.exists(FRAME_DIR):
            shutil.rmtree(FRAME_DIR)
        os.makedirs(FRAME_DIR)

    frames = [0]

    def capture_frame():
        doc.recompute()
        Gui.updateGui()
        if not RECORD_GIF:
            time.sleep(0.05)
            return
        view = Gui.ActiveDocument.ActiveView
        if view:
            scale = max(1, SUPERSAMPLE)
            view.saveImage(os.path.join(FRAME_DIR, f"frame_{frames[0]:04d}.png"),
                           FRAME_SIZE[0] * scale, FRAME_SIZE[1] * scale, "White")
            frames[0] += 1

    def hold(seconds):
        """Linger on the frame just captured.

        ffmpeg gives every frame of the sequence the same 1/FRAME_RATE on
        screen, so the way to stop the animation for a moment is to hand it the
        same picture several times over. Copy the file rather than re-rendering
        the view: the pixels are identical either way, and a screenshot per held
        frame would dominate the run time. It costs the GIF very little, since
        ffmpeg encodes each frame as a difference against the one before and
        the difference here is nothing at all.
        """
        if seconds <= 0:
            return
        if not RECORD_GIF:
            time.sleep(seconds)   # so the live preview pauses too
            return
        if frames[0] == 0:
            return
        last = os.path.join(FRAME_DIR, f"frame_{frames[0] - 1:04d}.png")
        for _ in range(max(1, round(seconds * FRAME_RATE))):
            shutil.copyfile(last, os.path.join(FRAME_DIR, f"frame_{frames[0]:04d}.png"))
            frames[0] += 1

    def place_all(placement_for):
        for item in moving_parts:
            item["obj"].Placement = placement_for(item)

    # Settle any pending expressions before reading the placements we restore to.
    doc.recompute()
    moving_parts = [{"obj": obj,
                     "orig": obj.Placement.copy(),
                     "saved": _release_placement(obj),
                     "rotated": None}
                    for obj in (carrier, blade)]

    # Never leave the document with its expressions stripped.
    try:
        swing_frames = max(1, SWING_FRAMES)
        pull_frames = max(1, PULL_FRAMES)
        return_swing = max(1, swing_frames // RETURN_SPEEDUP)
        return_pull = max(1, pull_frames // RETURN_SPEEDUP)

        def swing_to(angle):
            rot = App.Rotation(App.Vector(0, 0, 1), angle)
            # Rebuilt from the original placement every frame, so rounding
            # cannot accumulate across the animation.
            rot_placement = App.Placement(App.Vector(0, 0, 0), rot, pivot)
            place_all(lambda item: rot_placement.multiply(item["orig"]))

        # Open on the rack at rest, so the motion has something to start from.
        swing_to(0.0)
        capture_frame()
        hold(PAUSE_START)

        App.Console.PrintMessage("Swinging out...\n")
        for i in range(1, swing_frames + 1):
            swing_to((i / swing_frames) * SWING_ANGLE)
            capture_frame()
        hold(PAUSE_SWUNG)

        for item in moving_parts:
            item["rotated"] = item["obj"].Placement.copy()

        # Pull out along the swung-open direction, then reverse both legs.
        rad = math.radians(SWING_ANGLE)
        move_dir = App.Vector(-math.cos(rad), -math.sin(rad), 0)

        def slide_to(dist):
            trans = App.Placement(
                App.Vector(move_dir.x * dist, move_dir.y * dist, 0), App.Rotation())
            place_all(lambda item: trans.multiply(item["rotated"]))

        # Each leg below starts where the last one stopped, so skip its first
        # step: it would re-render a frame the pause is already holding.
        App.Console.PrintMessage("Pulling out of the slot...\n")
        for i in range(1, pull_frames + 1):
            slide_to(i * step_dist)
            capture_frame()
        hold(PAUSE_OUT)

        App.Console.PrintMessage("Sliding back in...\n")
        for i in range(return_pull - 1, -1, -1):
            slide_to((i / return_pull) * pull_frames * step_dist)
            capture_frame()

        App.Console.PrintMessage("Swinging back in...\n")
        for i in range(return_swing - 1, -1, -1):
            swing_to((i / return_swing) * SWING_ANGLE)
            capture_frame()
        hold(PAUSE_HOME)

        App.Console.PrintMessage("Animation complete!\n")
    finally:
        for item in moving_parts:
            _restore_placement(item["obj"], item["saved"], item["orig"])
        doc.recompute()

    _encode_gif(frames[0])


run_animation()
